TASTE-MONITORING DEFINITIONS AUTOMATIC TAGS ::=
BEGIN

TASTE-Peek ::= SEQUENCE {
	base-address	INTEGER (0..4294967295),  	-- 32bits type
	offset		INTEGER (-2147483648..2147483647),
	base-type	ENUMERATED { int-32, int-64, real-single, real-double, octet-string },
	nb-of-elements	INTEGER (1..10),		-- nb-of-elements EXCEPT for octet-string (1 element)
	sample-time	INTEGER (0..15)			-- in seconds
}

TASTE-Peek-list ::= SEQUENCE (SIZE (0..5)) OF TASTE-Peek

TASTE-Peek-id ::= INTEGER (0..4294967295)

TASTE-Peek-id-list ::= SEQUENCE (SIZE (1..10)) OF TASTE-Peek-id

TASTE-Monitoring-value ::= CHOICE {
	int-32		INTEGER (-2147483648 .. 2147483647) ,
	int-64		INTEGER (-9223372036854775807 .. 9223372036854775807),
	real-single	REAL (-100000000000000000000000000000000000000.0 .. 100000000000000000000000000000000000000.0),
	real-double 	REAL (-100000000000000000000000000000000000000000000000000000000000000000000000000000000000000000000000000000000000000000000000000000000000000000000000000000000000000000000000000000000000000000000000000000000000000000000000000000000000000000000000000000000000000000000000000000000000000000000000000000000000000000000.0 .. 100000000000000000000000000000000000000000000000000000000000000000000000000000000000000000000000000000000000000000000000000000000000000000000000000000000000000000000000000000000000000000000000000000000000000000000000000000000000000000000000000000000000000000000000000000000000000000000000000000000000000000000.0),
	octet-string	OCTET STRING (SIZE (0..10))
}

-- Result: memory value
TASTE-Monitoring ::= SEQUENCE {
	id	TASTE-Peek-id,
	values	SEQUENCE (SIZE (1..10)) OF TASTE-Monitoring-value
}

TASTE-Monitoring-list ::= SEQUENCE (SIZE (0..5)) OF TASTE-Monitoring

TASTE-Poke-list ::= TASTE-Monitoring-list

empty-peek-list TASTE-Peek-list ::= {}
empty-poke-list TASTE-Poke-list ::= {}

-- Type to hold a maximum number of peek values (defined in a context parameter, thus patchable)
TASTE-Peek-limit ::= INTEGER (0..1000)
END
